import Part
from FreeCAD import Base
from FreeCAD import Gui
import math
import BezCubic as BC

s=Gui.Selection.getSelectionEx()
line1=s[0].SubObjects[0].Curve
line2=s[1].SubObjects[0].Curve

p1=line1.StartPoint
p2=line1.EndPoint
p3=line2.StartPoint
p4=line2.EndPoint

if p1==p3 or p1==p4:
	pos=p1
	x=p2-p1
elif p2==p3 or p2==p4:
	pos=p2
	x=p1-p2

if p3==pos:
	yish=p4-p3
elif p4==pos:
	yish=p3-p4

x_copy=Base.Vector(x)
yish_copy=Base.Vector(yish)


sketch_x=x_copy.normalize()								# the actual x direction of the sketch
sketch_y_temp=yish_copy.normalize()						# something vaguely in the sketch's y direction
sketch_z=(sketch_x.cross(sketch_y_temp)).normalize()	# the actual z direction of the sketch
sketch_y=(sketch_z.cross(sketch_x)).normalize()			# the actual sketch's y direction

'''
##############################################################################
#test section
s_x=Part.Line(pos, pos+sketch_x)
s_y=Part.Line(pos, pos+sketch_y.scale(2,2,2))
s_z=Part.Line(pos, pos+sketch_z.scale(3,3,3))
Part.show(s_x.toShape())
Part.show(s_y.toShape())
Part.show(s_z.toShape())
#end test section
##############################################################################
'''
'''
sketch_matrix=App.Matrix(sketch_x.x,sketch_x.y,sketch_x.z,pos.x,
						sketch_y.x,sketch_y.y,sketch_y.z,pos.y,
						sketch_z.x,sketch_z.y,sketch_z.z,pos.z,
						0,0,0,1)
'''
#try flipping row/column of the rotation part of the matrix? the position part works above
sketch_matrix=App.Matrix(sketch_x.x,sketch_y.x,sketch_z.x,pos.x,
						sketch_x.y,sketch_y.y,sketch_z.y,pos.y,
						sketch_x.z,sketch_y.z,sketch_z.z,pos.z,
						0,0,0,1)

sk_mat_inverse=sketch_matrix.inverse()
sk_u=sk_mat_inverse.multiply(pos+x)
sk_v=sk_mat_inverse.multiply(pos+yish)


App.activeDocument().addObject('Sketcher::SketchObject','node')
App.ActiveDocument.node.Placement=App.Placement(sketch_matrix)
App.ActiveDocument.node.addGeometry(Part.Circle())
App.ActiveDocument.node.addGeometry(Part.Line(Base.Vector(0,0,0),sk_u))
App.ActiveDocument.node.addGeometry(Part.Line(Base.Vector(0,0,0),sk_v))
App.ActiveDocument.recompute()
