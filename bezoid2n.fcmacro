import Part
from FreeCAD import Base
from FreeCAD import Gui
import math
import NURBSlib_EVM as Nl

s=Gui.Selection.getSelectionEx()

if (len(s)!=2):
	print 'Select one & circle one point, then one & point one circle, from two sketches.'

node0=s[0]
node1=s[1]

circle0=node0.SubObjects[0].Curve.Center
point0=node0.SubObjects[1].Point

point1=node1.SubObjects[0].Point
circle1=node1.SubObjects[1].Curve.Center


pole0=[circle0,1]
pole1=[point0,1]
pole2=[point1,1]
pole3=[circle1,1]

poles = [pole0, pole1, pole2, pole3]

#first make a bezier
curve = Nl.Bezier_Cubic_curve(poles)

#then convert to bezoid
curve.increaseDegree(3)

start=curve.FirstParameter
end=curve.LastParameter

knot1=start+(end-start)/3.0
knot2=end-(end-start)/3.0

curve.insertKnot(knot1) 
curve.insertKnot(knot2)

raw_poles = curve.getPoles()
weights = curve.getWeights()

pole0=[raw_poles[0],weights[0]]
pole1=[raw_poles[1],weights[1]]
pole2=[raw_poles[2],weights[2]]	
pole3=[raw_poles[3],weights[3]]
pole4=[raw_poles[4],weights[4]]
pole5=[raw_poles[5],weights[5]]

poles = [pole0, pole1, pole2, pole3, pole4, pole5]

curve = Nl.NURBS_Cubic_6P_curve(poles)

Part.show(curve.toShape())






# below is an old inexact approximation. will be deleted after testing new version
''''
p0oid=p0								#same as bezier
p1oid=p0+(p1-p0).multiply(0.5)				#center of the first bezier leg
p12=(p1+p2).multiply(0.5)					#center of the middle bezier leg
p2oid=(p1oid+p12).multiply(0.5)				#center of the p1oid to p12 line
p4oid=p3+(p2-p3).multiply(0.5)				#center of the last bezier leg
p3oid=(p4oid+p12).multiply(0.5)	
p5oid=p3

# prepare the poles we will pass to the curve creation function
# pole = [Base.Vector, weight]
pole0=[ p0oid, 1]
pole1=[ p1oid, 1]
pole2=[ p2oid, 1]	
pole3=[ p3oid, 1]
pole4=[ p4oid, 1]
pole5=[ p5oid, 1]

ctrl1=Part.Line(p0oid, p1oid)
ctrl2=Part.Line(p1oid, p2oid)
ctrl3=Part.Line(p2oid, p3oid)
ctrl4=Part.Line(p3oid, p4oid)
ctrl5=Part.Line(p4oid, p5oid)

# prepare the pole list
poles = [pole0, pole1, pole2, pole3, pole4, pole5]


# create the cubic bezier curve from the poles (Part.BSplineCurve)
curve = Nl.SplineCubic6P_curve(poles)

Part.show(curve.toShape())
Part.show(ctrl1.toShape())
Part.show(ctrl2.toShape())
Part.show(ctrl3.toShape())
Part.show(ctrl4.toShape())
Part.show(ctrl5.toShape())
'''
