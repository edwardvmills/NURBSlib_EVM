import numpy as np


# BUGS? **************
# i don't really have enough verification data to tell if this is entirely correct for second, third, and higher derivatives.
# i'm going to use the second derivative at endpoints result [ 54, -81, 27 ] to try curvature matching on NURBS_Cubic_6p_curve.
# if that obviously fails, the next step is to generate test verification data to fix the algorithm below.

### calculating derivatives of NURBS curves. 
### the basis function derivatives form ratios of control points that control tangency, curvature, etc
### these ratios will allow tangency matching (trivial) and curvature matching (less trivial)
### across NURBS patches. Eventually, flow of curvature matching (not trivial at all) and all higher derivative continuity may follow.

### all formulas adapted from Piegl and Tiller. the dersbasisfun algorithm would be better, but my implementation appears to give bad results.
### until i can fix dersbasisfuns, the less efficient version here will have to do. dersbasisfuns is probably buried deep inside FreeCAD already
### in this file, all basis functions and derivatives are calculated, even if they are guaranteed to be zero in the knot span. 
### knot difference denominators are recalculated each time

### the functions so far:

# single basis function definition
# degree 0
# Ni0(i,U,u)

# single basis function of next degree
# Nip(i,p,U,u,Nipminus1)
# where Nipminus1 is a complete list of all basis functions of degree p-1

# all basis functions
# def Nips(p,U,u)
# return an array
# [	[ N00, N01, ..., N0p ],
# 	[ N10, N11, ..., N1p ],
#	...
#	[ Ni0, Ni1, ..., Nip ] ]

# derivative of single basis function. requires next lower derivatives to be available
#def dNipdu_(i,p,U,Nipminus1):
# for a first derivative of Ni,p, Nipminus1 is Ni,p-1
# for a higher derivative of Ni,p such as d(n)Ni(p)du(n), Nipminus1 is d(n-1)Ni(p-1)du(n-1)

# all derivatives. in progress
# dNipdus(p,U,u)
# spits out 
# [ [ N0p, N'op, N''0p, N'''0p ]
#   [ N1p, N'1p, N''1p, N'''1p ]
#   [ N2p, N'2p, N''2p, N'''2p ]
#   ...
#   [ Nip, N'ip, N''ip, N'''ip ] ]



# knot vector
a=1.0/3
b=2.0/3
#U=[0,0,0,0,1,1,1,1] # cubic bezier for reference
U=[0,0,0,0,a,b,1,1,1,1] # NURBS_Cubic_6P_curve type
#U=[0,0,0,1,2,3,4,4,5,5,5] # book example for testing
# degree
p=3

# parameter of interest. for endpoint analyis, either 0 or 0.999999 will do.
u=a


# single basis function definition
# degree 0
def Ni0(i,U,u):
	if u>=U[i] and u<U[i+1]:
		Ni0 = 1.0
	else:
		Ni0 = 0.0
	return Ni0

# degree +1
def Nip(i,p,U,u,Nipminus1):
	numerleft = (u-U[i])
	denomleft = (U[i+p]-U[i])
	if denomleft == 0.0:
		left = 0.0
	else:
		left = numerleft/denomleft
	numerright = (U[i+p+1]-u)
	denomright = (U[i+p+1]-U[i+1])
	if denomright == 0.0:
		right = 0.0
	else:
		right = numerright/denomright
	Nip= left*Nipminus1[i] + right*Nipminus1[i+1]
	return Nip

# all basis functions
def Nips(p,U,u):
	Nips = np.zeros((len(U)-1,p+1))
	# degree 0 basis functions
	for i in range(len(U)-1):
		Nips[i][0]=Ni0(i,U,u)
	for j in range(1,p+1):
		for i in range(len(U)-(1+j)):
			Nips[i][j]=Nip(i,j,U,u,Nips[:,j-1])
	return Nips

# derivative of single basis function. requires all lower derivatives to be available
def dNipdu(i,p,U,Nipminus1):
	# for a first derivative of Ni,p, Nipminus1 is Ni,p-1
	# for a higher derivative of Ni,p such as d(n)Ni(p)du(n), Nipminus1 is d(n-1)Ni(p-1)du(n-1)
	numerleft = p 
	denomleft = (U[i+p]-U[i])
	if denomleft == 0.0:
		left = 0.0
	else:
		left = numerleft/denomleft
	numerright = p 
	denomright = (U[i+p+1]-U[i+1])
	if denomright == 0.0:
		right = 0.0
	else:
		right = numerright/denomright
	dNipdu = left * Nipminus1[i] - right * Nipminus1[i+1]
	return dNipdu
#########################

# derivatives. compaction in progress


def dNipdus(p,U,u):
	# get the basis functions
	d0Nipdu0s = Nips(p,U,u)
	#print 'd0Nipdu0s= \n', d0Nipdu0s, '\n'
	
	# initialize an array for the first derivatives
	d1Nipdu1s = np.zeros((len(U)-1-1,p+1-1))
	for n in range(1,p+1):
		for i in range(len(U)-1-n):
			d1Nipdu1s[i][n-1]=dNipdu(i,n,U,d0Nipdu0s[:,n-1])
	#print 'd1Nipdu1s= \n', d1Nipdu1s,  '\n'
	
	d2Nipdu2s = np.zeros((len(U)-1-2,p+1-2))
	for n in range(2,p+1):
		for i in range(len(U)-1-n):
			d2Nipdu2s[i][n-2]=dNipdu(i,n,U,d1Nipdu1s[:,n-2])
	#print 'd2Nipdu2s= \n', d2Nipdu2s,  '\n'
	
	d3Nipdu3s = np.zeros((len(U)-1-3,p+1-3))
	for n in range(3,p+1):
		for i in range(len(U)-1-n):
			d3Nipdu3s[i][n-3]=dNipdu(i,n,U,d2Nipdu2s[:,n-3])
	#print 'd3Nipdu3s= \n', d3Nipdu3s,  '\n'
	
	
	dNipdus = np.zeros((len(U)-1,p+1))
	#print 'dNipdus= \n', dNipdus, '\n'
	dNipdus[:,0] = d0Nipdu0s[:,p-0]
	#print 'dNipdus= \n', dNipdus, '\n'
	dNipdus[0:-1,1] = d1Nipdu1s[:,p-1]
	#print 'dNipdus= \n', dNipdus, '\n'
	dNipdus[0:-2,2] = d2Nipdu2s[:,p-2]
	#print 'dNipdus= \n', dNipdus, '\n'
	dNipdus[0:-3,3] = d3Nipdu3s[:,p-3]
	
	return dNipdus


dNipdus(p,U,u)


'''
cubic bezier test:

>>> dNipdus(p,U,u)
d0Nipdu0s= 
[[ 0.  0.  0.  1.]
 [ 0.  0.  1.  0.]
 [ 0.  1.  0.  0.]
 [ 1.  0.  0.  0.]
 [ 0.  0.  0.  0.]
 [ 0.  0.  0.  0.]
 [ 0.  0.  0.  0.]]

d1Nipdu1s= 
[[ 0.  0. -3.]
 [ 0. -2.  3.]
 [-1.  2.  0.]
 [ 1.  0.  0.]
 [ 0.  0.  0.]
 [ 0.  0.  0.]]

d2Nipdu2s= 
[[  0.   6.]
 [  2. -12.]
 [ -4.   6.]
 [  2.   0.]
 [  0.   0.]]

d3Nipdu3s= 
[[ -6.]
 [ 18.]
 [-18.]
 [  6.]]

 NURBS_Cubic_6P_curve

# knot vector
a=1.0/3
b=2.0/3
U=[0,0,0,0,a,b,1,1,1,1]
# degree
p=3

# parameter of interest. for endpoint analyis, either 0 or 0.999999 will do.
u=0.0

>>> Nips(p,U,0)
array([[ 0.,  0.,  0.,  1.],
       [ 0.,  0.,  1.,  0.],
       [ 0.,  1.,  0.,  0.],
       [ 1.,  0.,  0.,  0.],
       [ 0.,  0.,  0.,  0.],
       [ 0.,  0.,  0.,  0.],
       [ 0.,  0.,  0.,  0.],
       [ 0.,  0.,  0.,  0.],
       [ 0.,  0.,  0.,  0.]])


>>> Nips(p,U,.5)
array([[ 0.     ,  0.     ,  0.     ,  0.     ],
       [ 0.     ,  0.     ,  0.     ,  0.03125],
       [ 0.     ,  0.     ,  0.125  ,  0.46875],
       [ 0.     ,  0.5    ,  0.75   ,  0.46875],
       [ 1.     ,  0.5    ,  0.125  ,  0.03125],
       [ 0.     ,  0.     ,  0.     ,  0.     ],
       [ 0.     ,  0.     ,  0.     ,  0.     ],
       [ 0.     ,  0.     ,  0.     ,  0.     ],
       [ 0.     ,  0.     ,  0.     ,  0.     ]])


>>> dNipdus(p,U,u)
d0Nipdu0s= 
[[ 0.  0.  0.  1.]
 [ 0.  0.  1.  0.]
 [ 0.  1.  0.  0.]
 [ 1.  0.  0.  0.]
 [ 0.  0.  0.  0.]
 [ 0.  0.  0.  0.]
 [ 0.  0.  0.  0.]
 [ 0.  0.  0.  0.]
 [ 0.  0.  0.  0.]]

d1Nipdu1s= 
[[ 0.  0. -9.]
 [ 0. -6.  9.]
 [-3.  6.  0.]
 [ 3.  0.  0.]
 [ 0.  0.  0.]
 [ 0.  0.  0.]
 [ 0.  0.  0.]
 [ 0.  0.  0.]]

d2Nipdu2s= 
[[  0.  54.]
 [ 18. -81.]
 [-27.  27.]
 [  9.   0.]
 [  0.   0.]
 [  0.   0.]
 [  0.   0.]]

d3Nipdu3s= 
[[-162. ]
 [ 283.5]
 [-148.5]
 [  27. ]
 [   0. ]
 [   0. ]]

>>> dNipdus(p,U,u)
array([[   1. ,   -9. ,   54. , -162. ],
       [   0. ,    9. ,  -81. ,  283.5],
       [   0. ,    0. ,   27. , -148.5],
       [   0. ,    0. ,    0. ,   27. ],
       [   0. ,    0. ,    0. ,    0. ],
       [   0. ,    0. ,    0. ,    0. ],
       [   0. ,    0. ,    0. ,    0. ],
       [   0. ,    0. ,    0. ,    0. ],
       [   0. ,    0. ,    0. ,    0. ]])



# example from book 
U=[0,0,0,1,2,3,4,4,5,5,5]
# degree
p=2

u=5.0/2

d0Nipdu0s= 
[[ 0.     0.     0.   ]
 [ 0.     0.     0.   ]
 [ 0.     0.     0.125]
 [ 0.     0.5    0.75 ]
 [ 1.     0.5    0.125]
 [ 0.     0.     0.   ]
 [ 0.     0.     0.   ]
 [ 0.     0.     0.   ]
 [ 0.     0.     0.   ]
 [ 0.     0.     0.   ]]		correct

d1Nipdu1s= 
[[ 0.   0. ]
 [ 0.   0. ]
 [ 0.  -0.5]
 [-1.   0. ]
 [ 1.   0.5]
 [ 0.   0. ]
 [ 0.   0. ]
 [ 0.   0. ]
 [ 0.   0. ]]		correct

d2Nipdu2s= 
[[ 0.]
 [ 0.]
 [ 1.]
 [-2.]
 [ 1.]
 [ 0.]
 [ 0.]
 [ 0.]]		correct

d3Nipdu3s= 
[]		should be all 0. kinda correct?

dNipdus= 
[[ 0.     0.     0.   ]
 [ 0.     0.     0.   ]
 [ 0.125 -0.5    1.   ]
 [ 0.75   0.    -2.   ]
 [ 0.125  0.5    1.   ]
 [ 0.     0.     0.   ]
 [ 0.     0.     0.   ]
 [ 0.     0.     0.   ]
 [ 0.     0.     0.   ]
 [ 0.     0.     0.   ]] i think this is correct

'''
