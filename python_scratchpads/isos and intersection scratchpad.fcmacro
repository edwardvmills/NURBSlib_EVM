import Part
from FreeCAD import Base
from FreeCAD import Gui
import math
import BezCubic as BC


u5=s.uIso(0.5)

>>> s=Gui.Selection.getSelectionEx()[0].SubObjects[0]
<Edge object at 0x33ca440>
>>> s.Curve
<BezierCurve object>
>>> s0=s.Curve
>>> s0
<BezierCurve object>
>>> s0.intersect2d
<built-in method intersect2d of Part.GeomBezierCurve object at 0x387c388>
>>> s=Gui.Selection.getSelectionEx()[0].SubObjects[0]
>>> s1=s.Curve
>>> s1
<BezierCurve object>
>>> s1.intersect2d(s0)
Traceback (most recent call last):
  File "<input>", line 1, in <module>
TypeError: function takes exactly 2 arguments (1 given)
>>> Part.Plane(Base.vector


>>> s=Gui.Selection.getSelectionEx()[0].SubObjects[0].Surface
>>> s
<BezierSurface object>
>>> seg=s
>>> seg
<BezierSurface object>
>>> seg.segment(0.1,0.5,0.4,0.9)
>>> Part.show(seg.toShape())
