import Part
from FreeCAD import Base
from FreeCAD import Gui
import math
import NURBSlib_EVM as Nl


s=Gui.Selection.getSelection()

if (len(s)!=3) and (len(s)!=4):
	print 'select 3 or 4 cubic bezier curves that form a loop counterclockwise. with 3 curves, the corner from first to last will be degenerate'


if (len(s)==3):
	bez1=s[0].Shape.Curve
	bez2=s[1].Shape.Curve
	bez3=s[2].Shape.Curve
	quad_patch = Nl.tri_quad_patch(bez1,bez2,bez3)
	mid_edge_poly = Nl.mid_edge_poly(quad_patch)
	for i in range(len(mid_edge_poly)):
		Part.show(mid_edge_poly[i].toShape())

elif (len(s)==4):
	bez1=s[0].Shape.Curve
	bez2=s[1].Shape.Curve
	bez3=s[2].Shape.Curve
	bez4=s[3].Shape.Curve
	quad_patch = Nl.quad_patch(bez1,bez2,bez3,bez4)
	mid_edge_poly = Nl.mid_edge_poly(quad_patch)
	for i in range(len(mid_edge_poly)):
		Part.show(mid_edge_poly[i].toShape())
