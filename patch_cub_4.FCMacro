import Part
from FreeCAD import Base
from FreeCAD import Gui
import math
import BezCubic as BC


s=Gui.Selection.getSelection()

if (len(s)!=4):
	print 'select four cubic bezier curves that form a loop counterclockwise'

bez1=s[0].Shape.Curve
bez2=s[1].Shape.Curve
bez3=s[2].Shape.Curve
bez4=s[3].Shape.Curve

quad_patch1=BC.quad_patch(bez1,bez2,bez3,bez4)

bezpatch1 = BC.BezCubic_patch(quad_patch1)

Part.show(bezpatch1.toShape())
