import Part
from FreeCAD import Base
from FreeCAD import Gui
import math
import BezCubic as BC

# Creates a cubic bezier spline from 3 selected lines connected 1>2>3 within the same sketch.
# The first and last lines  define the start point, end point, start tangent, and end tangent.
# The middle line mostly serves as a selection aid, but can be useful for visualization of the control polygon.

#get selection contents
s=Gui.Selection.getSelectionEx()[0].SubObjects

# check basic contents of selection (seems broken right now, doesn't go to report view)
if (len(s)!=3):
	print 'Select three connected lines from one sketch (in order). Hide other elements as necessary to get the right selection'



line0=s[0].Curve # a Part.Line object
line1=s[1].Curve # a Part.Line object
line2=s[2].Curve # a Part.Line object

#orient the line endpoints to proceed from one end of the connected lines to the other. Checks for proper connection along the way
seg0=BC.orient_a_to_b([line0.StartPoint,line0.EndPoint],[line1.StartPoint,line1.EndPoint])
seg1=BC.orient_a_to_b([line1.StartPoint,line1.EndPoint],[line2.StartPoint,line2.EndPoint])
seg2_reverse=BC.orient_a_to_b([line2.StartPoint,line2.EndPoint],[line1.StartPoint,line1.EndPoint])

# prepare the poles we will pass to the curve creation function
# pole = [Base.Vector, weight]
pole0=[seg0[0],1]
pole1=[seg1[0],1]
pole2=[seg2_reverse[1],1]	
pole3=[seg2_reverse[0],1]

# prepare the pole list
poles = [pole0, pole1, pole2, pole3]

# create the cubice bezier curve from the poles (Part.BSplineCurve)
curve = BC.BezCubic_curve(poles)

Part.show(curve.toShape())
