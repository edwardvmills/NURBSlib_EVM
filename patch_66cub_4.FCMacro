import Part
from FreeCAD import Base
from FreeCAD import Gui
import math
import NURBSlib_EVM as Nl


s=Gui.Selection.getSelection()

if (len(s)!=4):
	print 'select four bezoid curves that form a loop counterclockwise'

bez1=s[0].Shape.Curve
bez2=s[1].Shape.Curve
bez3=s[2].Shape.Curve
bez4=s[3].Shape.Curve


quad66_patch=Nl.quad66_patch(bez1,bez2,bez3,bez4)
patch66=Nl.BezCubic66_patch(quad66_patch)

Part.show(patch66.toShape())
