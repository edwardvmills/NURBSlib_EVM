import Part
from FreeCAD import Base
from FreeCAD import Gui
import math
import BezCubic as BC


sel=Gui.Selection.getSelectionEx()[0]
edge=sel.SubObjects[0]
nurbs=edge.toNurbs()
curve=nurbs.Edge1.Curve

curve.increaseDegree(3)

raw_poles = curve.getPoles()
weights = curve.getWeights()


pole0=[raw_poles[0],weights[0]]
pole1=[raw_poles[1],weights[1]]
pole2=[raw_poles[2],weights[2]]	
pole3=[raw_poles[3],weights[3]]

poles = [pole0, pole1, pole2, pole3]

curve = BC.BezCubic_curve(poles)

Part.show(curve.toShape())
