import Part
from FreeCAD import Base
from FreeCAD import Gui
import math
import NURBSlib_EVM as Nl


#the input is 4 points, like a bezier cubic curve.
#two additional control points are inserted, and the knot vector extened, in a way that tries to mimick the bezier of the four original points.
#the two additional control points can be manipulated to control the curvature at each endpoint.

# Creates a cubic spline from 3 selected lines connected 1>2>3 within the same sketch.
# The first and last lines  define the start point, end point, start tangent, and end tangent.
# The middle line mostly serves to specify end points, but can be useful for visualization of the control polygon.

#get selection contents
s=Gui.Selection.getSelectionEx()[0].SubObjects

# check basic contents of selection (seems broken right now, doesn't go to report view)
if (len(s)!=3):
	print 'Select three connected lines from one sketch (in order). Hide other elements as necessary to get the right selection'


line0=s[0].Curve # a Part.Line object
line1=s[1].Curve # a Part.Line object
line2=s[2].Curve # a Part.Line object

#orient the line endpoints to proceed from one end of the connected lines to the other. Checks for proper connection along the way
seg0=BC.orient_a_to_b([line0.StartPoint,line0.EndPoint],[line1.StartPoint,line1.EndPoint])
seg1=BC.orient_a_to_b([line1.StartPoint,line1.EndPoint],[line2.StartPoint,line2.EndPoint])
seg2_reverse=BC.orient_a_to_b([line2.StartPoint,line2.EndPoint],[line1.StartPoint,line1.EndPoint])

p0=seg0[0]
p1=seg1[0]
p2=seg2_reverse[1]
p3=seg2_reverse[0]

poles = [p0, p1, p2, p3]

#first make a bezier
curve = Nl.Bezier_Cubic_curve(poles)

#then convert to bezoid
curve.increaseDegree(3)

start=curve.FirstParameter
end=curve.LastParameter

knot1=start+(end-start)/3.0
knot2=end-(end-start)/3.0

curve.insertKnot(knot1) 
curve.insertKnot(knot2)

raw_poles = curve.getPoles()
weights = curve.getWeights()

pole0=[raw_poles[0],weights[0]]
pole1=[raw_poles[1],weights[1]]
pole2=[raw_poles[2],weights[2]]	
pole3=[raw_poles[3],weights[3]]
pole4=[raw_poles[4],weights[4]]
pole5=[raw_poles[5],weights[5]]

poles = [pole0, pole1, pole2, pole3, pole4, pole5]

curve = Nl.NURBS_Cubic_6P_curve(poles)

Part.show(curve.toShape())

Part.show(ctrl2.toShape())
Part.show(ctrl3.toShape())
Part.show(ctrl4.toShape())
Part.show(ctrl5.toShape())
