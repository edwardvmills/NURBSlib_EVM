import Part
from FreeCAD import Base
from FreeCAD import Gui
import math
import NURBSlib_EVM as Nl

# OBSOLETE. replaced by curve_cubic_3_lines. uses the same sketches, much easier selection.
# this is NOT a general purpose 'any old 4 points will do' selection mechanism.

s=Gui.Selection.getSelectionEx()[0].SubObjects

if (len(s)!=4):
	print 'Select four vertices from one sketch. Hide other elements as necessary to get the right selection'
	

pole0=[s[0].Point,1]
pole1=[s[1].Point,1]
pole2=[s[2].Point,1]	
pole3=[s[3].Point,1]

poles = [pole0, pole1, pole2, pole3]

curve = Nl.Bezier_Cubic_curve(poles)

Part.show(curve.toShape())
