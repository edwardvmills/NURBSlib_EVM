import Part
from FreeCAD import Base
from FreeCAD import Gui
import math
import NURBSlib_EVM as Nl

# given the first three control points of a non-rational cubic Bezier curve (knots [0,0,0,0,1,1,1,1]), 
# this macro calculates the radius of curvature at the first point, and draws a circle of said radius in
# in the osculating plane.


s=Gui.Selection.getSelectionEx()[0].SubObjects

if (len(s)!=3):
	print 'Select 3 vertices from one sketch. Hide other elements as necessary to get the right selection'

pole0=[s[0].Point,1]
pole1=[s[1].Point,1]
pole2=[s[2].Point,1]	

curvature = Nl.Cubic_Bezier_curvature(pole0[0], pole1[0], pole2[0])
radius = 1/curvature

v1=pole1[0]-pole0[0]
v2=pole2[0]-pole1[0]
curvature_plane_normal = (v2.cross(v1)).normalize()
curvature_center_direction = (v1.cross(curvature_plane_normal)).normalize()
curvature_center = pole0[0] + curvature_center_direction.multiply(radius)

normal=Part.Line(pole0[0], pole0[0]+curvature_plane_normal)
center_direction = Part.Line(pole0[0], pole0[0]+curvature_center_direction)
circle=Part.makeCircle(radius, curvature_center, curvature_plane_normal, 0,360)

#Part.show(normal.toShape())
#Part.show(center_direction.toShape())
Part.show(circle)
 
print curvature
print radius
