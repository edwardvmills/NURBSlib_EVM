import Part
from FreeCAD import Base
from FreeCAD import Gui
import math



curve=Gui.Selection.getSelectionEx()[0].SubObjects[0].Curve

print curve.__class__
print 'Degree: ', curve.Degree
print 'Knot Sequence: ', curve.KnotSequence
print curve.NbPoles, ' Poles'
