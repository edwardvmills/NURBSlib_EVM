#    This file is part of NURBSLib_EVM
#    (c) Edward Mills 2016
#    edwardvmills@gmail.com
#
#    NURBSLib_EVM is free software: you can redistribute it and/or modify
#    it under the terms of the GNU General Public License as published by
#    the Free Software Foundation, either version 3 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program.  If not, see <http://www.gnu.org/licenses/>.


from __future__ import division # allows floating point division from integers
import FreeCAD, Part, math
from FreeCAD import Base
from FreeCAD import Gui
import NURBSlib_EVM as Nl

sel=Gui.Selection.getSelection()
if len(sel)==1:
	try:
		if sel[0].Shape.Curve.NbPoles==4:
			mode='Bezier'
	except Exception: 
		pass
	try:
		if sel[0].GeometryCount==5:
			mode='5L'
	except Exception: 
		pass
	try:
		if sel[0].GeometryCount==1:
			#if isinstance(sel[0].Geometry[0], Part.ArcOfCircle):
			mode='Arc'
	except Exception: 
		pass
if len(sel)==2:
	if  sel[0].TypeId=='Sketcher::SketchObject' and sel[1].TypeId=='Sketcher::SketchObject':
		mode='2N'
	if sel[0].Shape.Curve.NbPoles==4 and sel[1].Shape.Curve.NbPoles==4:
		mode='FilletBezier'

print 'selection processed as ', mode, ' operation'

if mode=='5L':
	sketch=Gui.Selection.getSelection()[0]
	a=FreeCAD.ActiveDocument.addObject("Part::FeaturePython","ControlPoly6_5L")
	Nl.ControlPoly6_5L(a,sketch)
	a.ViewObject.Proxy=0 # just set it to something different from None (this assignment is needed to run an internal notification)
	FreeCAD.ActiveDocument.recompute()

if mode=='Arc':
	sketch=Gui.Selection.getSelection()[0]
	a=FreeCAD.ActiveDocument.addObject("Part::FeaturePython","ControlPoly6_Arc")
	Nl.ControlPoly6_Arc(a,sketch)
	a.ViewObject.Proxy=0 # just set it to something different from None (this assignment is needed to run an internal notification)
	FreeCAD.ActiveDocument.recompute()

if mode=='Bezier':
	bezier=Gui.Selection.getSelection()[0]
	a=FreeCAD.ActiveDocument.addObject("Part::FeaturePython","ControlPoly6_Bezier")
	Nl.ControlPoly6_Arc(a,bezier)
	a.ViewObject.Proxy=0 # just set it to something different from None (this assignment is needed to run an internal notification)
	FreeCAD.ActiveDocument.recompute()

if mode=='2N':
	sketch0=Gui.Selection.getSelection()[0]
	sketch1=Gui.Selection.getSelection()[1]
	a=FreeCAD.ActiveDocument.addObject("Part::FeaturePython","ControlPoly6_2N")
	Nl.ControlPoly6_2N(a,sketch0,sketch1)
	a.ViewObject.Proxy=0 # just set it to something different from None (this assignment is needed to run an internal notification)
	FreeCAD.ActiveDocument.recompute()

if mode=='FilletBezier':
	CubicCurve4_0=Gui.Selection.getSelection()[0]
	CubicCurve4_1=Gui.Selection.getSelection()[1]
	a=FreeCAD.ActiveDocument.addObject("Part::FeaturePython","ControlPoly6_FilletBezier")
	Nl.ControlPoly6_FilletBezier(a,CubicCurve4_0,CubicCurve4_1)
	a.ViewObject.Proxy=0 # just set it to something different from None (this assignment is needed to run an internal notification)
	FreeCAD.ActiveDocument.recompute()
