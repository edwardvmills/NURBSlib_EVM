import Part
from FreeCAD import Base
from FreeCAD import Gui
import math
import NURBSlib_EVM as Nl
import copy

doc=App.activeDocument()
curve=Gui.Selection.getSelectionEx()[0].SubObjects[0].Curve
surf=Gui.Selection.getSelectionEx()[1].SubObjects[0].Surface

# get the curve-surface intersection
isect = Nl..isect_curve_surf(curve, surf)
point_isect = isect[0]
curve_isect_u = isect[1]
surf_isect_uv = isect[2]

# subdivide the curve
curve_0u = curve.copy()
curve_0u.segment(curve.FirstParameter, curve_isect_u)

curve_u1 = curve.copy()
curve_u1.segment(curve_isect_u, curve.LastParameter)

# add group for sub curves
curve_grp=doc.addObject("App::DocumentObjectGroup", "Sub Curves")
doc_curve_0u=doc.addObject("Part::Feature","curve_0u")
curve_grp.addObject(doc_curve_0u) 
doc_curve_0u.Shape=curve_0u.toShape() 
doc_curve_u1=doc.addObject("Part::Feature","curve_u1")
curve_grp.addObject(doc_curve_u1)
doc_curve_u1.Shape=curve_u1.toShape() 

# subdivide the surface



doc.recompute()
