#    This file is part of NURBSLib_EVM
#    (c) Edward Mills 2016
#    edwardvmills@gmail.com
#
#    NURBSLib_EVM is free software: you can redistribute it and/or modify
#    it under the terms of the GNU General Public License as published by
#    the Free Software Foundation, either version 3 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program.  If not, see <http://www.gnu.org/licenses/>.


from __future__ import division # allows floating point division from integers
import FreeCAD, Part, math
from FreeCAD import Base
from FreeCAD import Gui
import NURBSlib_EVM as Nl

sel=Gui.Selection.getSelection()
if len(sel)==4:
	mode='4sided'
elif len(sel)==3:
	mode='3sided'

if mode=='4sided':
	poly0=Gui.Selection.getSelection()[0]
	poly1=Gui.Selection.getSelection()[1]
	poly2=Gui.Selection.getSelection()[2]
	poly3=Gui.Selection.getSelection()[3]
	a=FreeCAD.ActiveDocument.addObject("Part::FeaturePython","ControlGrid64_4")
	Nl.ControlGrid64_4(a,poly0, poly1, poly2, poly3)
	a.ViewObject.Proxy=0 # just set it to something different from None (this assignment is needed to run an internal notification)
	FreeCAD.ActiveDocument.recompute()

if mode=='3sided':
	poly0=Gui.Selection.getSelection()[0]
	poly1=Gui.Selection.getSelection()[1]
	poly2=Gui.Selection.getSelection()[2]
	a=FreeCAD.ActiveDocument.addObject("Part::FeaturePython","ControlGrid64_3")
	Nl.ControlGrid64_3(a,poly0, poly1, poly2)
	a.ViewObject.Proxy=0 # just set it to something different from None (this assignment is needed to run an internal notification)
	FreeCAD.ActiveDocument.recompute()
