import Part
from FreeCAD import Base
from FreeCAD import Gui
import math
import NURBSlib_EVM as Nl


s=Gui.Selection.getSelection()

if (len(s)!=3) and (len(s)!=4):
	print 'select 3 or 4 cubic bezier curves that form a loop counterclockwise. with 3 curves, the corner from first to last will be degenerate'


if (len(s)==3):
	bez1=s[0].Shape.Curve
	bez2=s[1].Shape.Curve
	bez3=s[2].Shape.Curve
	grid_44 = Nl.grid_44_tri_alt(bez1,bez2,bez3)
	poly_grid_44 = Nl.poly_grid_44(grid_44)
	for i in range(len(poly_grid_44)):
		Part.show(poly_grid_44[i].toShape())

elif (len(s)==4):
	bez1=s[0].Shape.Curve
	bez2=s[1].Shape.Curve
	bez3=s[2].Shape.Curve
	bez4=s[3].Shape.Curve
	grid_44 = Nl.grid_44_quad(bez1,bez2,bez3,bez4)
	poly_grid_44 = Nl.poly_grid_44(grid_44)
	for i in range(len(poly_grid_44)):
		Part.show(poly_grid_44[i].toShape())
