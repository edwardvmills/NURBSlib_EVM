#    This file is part of NURBSLib_EVM
#    (c) Edward Mills 2016
#    edwardvmills@gmail.com
#
#    NURBSLib_EVM is free software: you can redistribute it and/or modify
#    it under the terms of the GNU General Public License as published by
#    the Free Software Foundation, either version 3 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program.  If not, see <http://www.gnu.org/licenses/>.


from __future__ import division # allows floating point division from integers
import FreeCAD, Part, math
from FreeCAD import Base
from FreeCAD import Gui
import NURBSlib_EVM as Nl

sel=Gui.Selection.getSelection()
if len(sel)==1:
	if sel[0].GeometryCount==3:
		mode='3L'
	else: #if sel[0].GeometryCount==1 or sel[0].GeometryCount==8:
		mode='Arc'
elif len(sel)==2:
	mode='2N'
print mode
if mode=='3L':
	sketch=Gui.Selection.getSelection()[0]
	a=FreeCAD.ActiveDocument.addObject("Part::FeaturePython","ControlPoly4_3L")
	Nl.ControlPoly4_3L(a,sketch)
	a.ViewObject.Proxy=0 # just set it to something different from None (this assignment is needed to run an internal notification)
	FreeCAD.ActiveDocument.recompute()

if mode=='Arc':
	sketch=Gui.Selection.getSelection()[0]
	a=FreeCAD.ActiveDocument.addObject("Part::FeaturePython","ControlPoly4_Arc")
	Nl.ControlPoly4_Arc(a,sketch)
	a.ViewObject.Proxy=0 # just set it to something different from None (this assignment is needed to run an internal notification)
	FreeCAD.ActiveDocument.recompute()

if mode=='2N':
	sketch0=Gui.Selection.getSelection()[0]
	sketch1=Gui.Selection.getSelection()[1]
	a=FreeCAD.ActiveDocument.addObject("Part::FeaturePython","ControlPoly4_2N")
	Nl.ControlPoly4_2N(a,sketch0,sketch1)
	a.ViewObject.Proxy=0 # just set it to something different from None (this assignment is needed to run an internal notification)
	FreeCAD.ActiveDocument.recompute()
