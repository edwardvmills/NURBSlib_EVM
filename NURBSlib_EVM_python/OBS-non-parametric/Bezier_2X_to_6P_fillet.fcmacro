import Part
from FreeCAD import Base
from FreeCAD import Gui
from PySide import QtGui
import math
import NURBSlib_EVM as Nl

# get selection
sel=Gui.Selection.getSelectionEx()

curve_0 = sel[0].SubObjects[0].Curve # first selected curve
curve_1 = sel[1].SubObjects[0].Curve # second selected curve

NURBS_6P_0=curve_0.copy() # make copy to keep original selection intact
NURBS_6P_0.insertKnot(1.0/3.0) # add knots to convert bezier to 6P
NURBS_6P_0.insertKnot(2.0/3.0)

NURBS_6P_1=curve_1.copy() # make copy to keep original selection intact
NURBS_6P_1.insertKnot(1.0/3.0) # add knots to convert bezier to 6P
NURBS_6P_1.insertKnot(2.0/3.0)

# get all poles and weights
poles_0=NURBS_6P_0.getPoles()
weights_0=NURBS_6P_0.getWeights()
poles_1=NURBS_6P_1.getPoles()
weights_1=NURBS_6P_1.getWeights()

# get all start/end points of the curves to determine how they are connected
p00 = curve_0.StartPoint
p01 = curve_0.EndPoint
p10 = curve_1.StartPoint
p11 = curve_1.EndPoint

if p00==p10: 
	p0=[poles_0[5],weights_0[5]]
	p1=[poles_0[4],weights_0[4]]
	p2=[poles_0[3],weights_0[3]]
	p3=[poles_1[3],weights_0[3]]
	p4=[poles_1[4],weights_0[4]]
	p5=[poles_1[5],weights_0[5]]

if p00==p11:
	p0=[poles_0[5],weights_0[5]]
	p1=[poles_0[4],weights_0[4]]
	p2=[poles_0[3],weights_0[3]]
	p3=[poles_1[2],weights_0[2]]
	p4=[poles_1[1],weights_0[1]]
	p5=[poles_1[0],weights_0[0]]

if p01==p10:
	p0=[poles_0[0],weights_0[0]]
	p1=[poles_0[1],weights_0[1]]
	p2=[poles_0[2],weights_0[2]]
	p3=[poles_1[3],weights_0[3]]
	p4=[poles_1[4],weights_0[4]]
	p5=[poles_1[5],weights_0[5]]

if p01==p11:
	p0=[poles_0[0],weights_0[0]]
	p1=[poles_0[1],weights_0[1]]
	p2=[poles_0[2],weights_0[2]]
	p3=[poles_1[2],weights_0[2]]
	p4=[poles_1[1],weights_0[1]]
	p5=[poles_1[0],weights_0[0]]

# at this stage, the poles are clustered around the curve start and end. They need to get 'spread out' a bit

'''
#### first version
# scale innermost control points along the start/end tanegnts. this maintains the endpoint curvature (without needing to even calculate it). 
# ok...but not great. the first segment (tangent control) appears small compared to the rest of the control polygon.
# curvature combs show really severe G3 problems

instructions = "pulls the fillet closer to the input curve \n recommend 0-5 range"

scale_0=QtGui.QInputDialog.getDouble(None, "keep fillet close to first leg factor", instructions,value=2.0, decimals=16)[0]
scale_1=QtGui.QInputDialog.getDouble(None, "keep fillet close to second leg factor", instructions,value=2.0, decimals=16)[0]

tan_0 = p1[0]-p0[0]
tan_1 = p4[0]-p5[0]

p2_scl = [p2[0] + tan_0.multiply(scale_0), p2[1]]
p3_scl = [p3[0] + tan_1.multiply(scale_1), p3[1]]
'''

#### second version

#### find start/end curvatures, scale start and end tangents, then reposition innermost control points to maintain curvature. 
#### set the height to the tangent, but leave the length along the tangent as numeric input. what to use for a start value?

scale_0 = 2.0 # factor to scale first control leg by.
scale_4 = 2.0 # factor to scale last control leg by.

### calculate curvature components
## start point
l0 = p1[0]-p0[0]					# first control leg
tan0=Base.Vector(l0)				# make clean copy
tan0.normalize()					# unit tangent direction
l1=Base.Vector(tan0)				# make clean copy
l1.multiply(tan0.dot(p2[0]-p1[0])) 	# scalar projection of second control leg along unit tangent
h1=(p2[0]-p1[0])-l1				# height of second control leg orthogonal to tangent
## end point
l4 = p4[0]-p5[0]					# last control leg
tan4=Base.Vector(l4)				# make clean copy
tan4.normalize()					# unit tangent direction
l3=Base.Vector(tan4)				# make clean copy
l3.multiply(tan4.dot(p3[0]-p4[0])) 	# scalar projection of second to last control leg along unit tangent
h3=(p3[0]-p4[0])-l3				# height of second control leg orthogonal to tangent

### scale first and last control legs
L0=Base.Vector(l0)			# make clean copy
L0.multiply(scale_0)		# apply tangent scale
p1_scl = [p0[0] + L0, p1[1]]	# reposition second control point

L4=Base.Vector(l4)			# make clean copy
L4.multiply(scale_4)		# apply tangent scale
p4_scl = [p5[0] + L4, p4[1]]	# reposition fifth control point

### calc new heights for inner control legs
H1 = Base.Vector(h1)				# make clean copy
H1.multiply(scale_0.__pow__(2))	# apply height scale

H3 = Base.Vector(h3)				# make clean copy
H3.multiply(scale_4.__pow__(2))	# apply height scale

### take input and calc new tangential component for  inner control points
instructions = "pulls the fillet closer to the input tangents \n recommend 0-5 range"

scale_1=QtGui.QInputDialog.getDouble(None, "keep fillet close to first leg factor", instructions,value=2.0, decimals=16)[0]
scale_3=QtGui.QInputDialog.getDouble(None, "keep fillet close to last leg factor", instructions,value=2.0, decimals=16)[0]

L1 = Base.Vector(l1) 			# make clean copy
L1 = L1.multiply(scale_1)		# apply inner tangent scale
p2_scl = [p1[0] + H1 + L1, p2[1]]	#reposition third control point

L3 = Base.Vector(l3) 			# make clean copy
L3 = L3.multiply(scale_3)		# apply inner tangent scale
p3_scl = [p4[0] + H3 + L3, p3[1]]	#reposition third control point



poles = [p0, p1_scl, p2_scl, p3_scl, p4_scl, p5]

# create the NURBS 6P cubic curve as the fillet approximation
fillet = Nl.NURBS_Cubic_6P_curve(poles)

Part.show(fillet.toShape())
